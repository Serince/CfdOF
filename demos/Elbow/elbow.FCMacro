# -*- coding: utf-8 -*-

import os
FreeCAD.open(os.path.join(os.path.dirname(__file__), "elbow.fcstd"))
Gui.SendMsgToActiveView("ViewFit")

Gui.activateWorkbench("CfdOFWorkbench")
import CfdAnalysis
import CfdTools
analysis = CfdAnalysis.makeCfdAnalysis('CfdAnalysis')
CfdTools.setActiveAnalysis(analysis)
import CfdPhysicsSelection
analysis.addObject(CfdPhysicsSelection.makeCfdPhysicsSelection())
import core.materials.CfdFluidMaterial as CfdFluidMaterial
analysis.addObject(CfdFluidMaterial.makeCfdFluidMaterial('FluidProperties'))
import CfdInitialiseFlowField
analysis.addObject(CfdInitialiseFlowField.makeCfdInitialFlowField())
import CfdSolverFoam
analysis.addObject(CfdSolverFoam.makeCfdSolverFoam())
import CfdMesh
CfdMesh.makeCfdMesh('Pad_Mesh')
App.ActiveDocument.ActiveObject.Part = App.ActiveDocument.Pad
CfdTools.getActiveAnalysis().addObject(App.ActiveDocument.ActiveObject)

FreeCAD.ActiveDocument.Pad_Mesh.CharacteristicLengthMax = '800 mm'
FreeCAD.ActiveDocument.Pad_Mesh.MeshUtility = 'cfMesh'
FreeCAD.ActiveDocument.Pad_Mesh.ElementDimension = '2D'
FreeCAD.ActiveDocument.Pad_Mesh.CellsBetweenLevels = 3
FreeCAD.ActiveDocument.Pad_Mesh.EdgeRefinement = 1.0
FreeCAD.ActiveDocument.Pad_Mesh.PointInMesh = {'x': '0 mm', 'y': '0 mm', 'z': '0 mm'}

import CfdMeshRefinement
CfdMeshRefinement.makeCfdMeshRefinement(App.ActiveDocument.Pad_Mesh)
obj = FreeCAD.ActiveDocument.MeshRefinement
obj.Extrusion = True
obj.ExtrusionType = '2DPlanar'
obj.ExtrusionThickness = '1000.0 mm'
FreeCAD.ActiveDocument.MeshRefinement.ShapeRefs = [
(FreeCAD.ActiveDocument.getObject('Pad'), ('Face14',))]
FreeCAD.ActiveDocument.recompute()

obj = FreeCAD.ActiveDocument.PhysicsModel
obj.Time = 'Steady'
obj.Flow = 'Incompressible'
obj.Thermal = 'None'
obj.Turbulence = 'Laminar'
obj.gx = '0 mm/s^2'
obj.gy = '-9810 mm/s^2'
obj.gz = '0 mm/s^2'

FreeCAD.ActiveDocument.FluidProperties.Material = {'Name': 'Air', 'Description': 'Standard air properties at 20 Degrees Celsius and 1 atm', 'Density': '1.20 kg/m^3', 'DynamicViscosity': '1.80e-5 kg/m/s', 'MolarMass': '0.0289643897748887 kg/mol', 'Cp': '1004.703 J/kg/K', 'SutherlandConstant': '1.4579326545176254e-06 kg/m/s/K^0.5', 'SutherlandTemperature': '110.4 K'}

import CfdFluidBoundary
CfdTools.getActiveAnalysis().addObject(CfdFluidBoundary.makeCfdFluidBoundary())
bc = FreeCAD.ActiveDocument.CfdFluidBoundary
bc.BoundaryType = 'inlet'
bc.BoundarySubType = 'uniformVelocityInlet'
bc.ThermalBoundaryType = 'fixedValue'
bc.VelocityIsCartesian = True
bc.Ux = '1000 mm/s'
bc.Uy = '0 mm/s'
bc.Uz = '0 mm/s'
bc.Temperature = '293 K'
FreeCAD.ActiveDocument.CfdFluidBoundary.Label = 'inlet'
FreeCAD.ActiveDocument.CfdFluidBoundary.ShapeRefs = [
(FreeCAD.ActiveDocument.getObject('Pad'),('Face2',))]
FreeCAD.ActiveDocument.recompute()

CfdTools.getActiveAnalysis().addObject(CfdFluidBoundary.makeCfdFluidBoundary())
bc = FreeCAD.ActiveDocument.CfdFluidBoundary001
bc.BoundaryType = 'inlet'
bc.BoundarySubType = 'uniformVelocityInlet'
bc.ThermalBoundaryType = 'fixedValue'
bc.VelocityIsCartesian = True
bc.Ux = '0 mm/s'
bc.Uy = '3000 mm/s'
bc.Uz = '0 mm/s'
bc.Temperature = '293 K'
FreeCAD.ActiveDocument.CfdFluidBoundary001.Label = 'inlet2'
FreeCAD.ActiveDocument.CfdFluidBoundary001.ShapeRefs = [
(FreeCAD.ActiveDocument.getObject('Pad'),('Face10',))]
FreeCAD.ActiveDocument.recompute()

CfdTools.getActiveAnalysis().addObject(CfdFluidBoundary.makeCfdFluidBoundary())
bc = FreeCAD.ActiveDocument.CfdFluidBoundary002
bc.BoundaryType = 'wall'
bc.BoundarySubType = 'fixedWall'
bc.ThermalBoundaryType = 'fixedValue'
bc.VelocityIsCartesian = True
bc.Ux = '0 mm/s'
bc.Uy = '0 mm/s'
bc.Uz = '0 mm/s'
bc.Temperature = '293 K'
FreeCAD.ActiveDocument.CfdFluidBoundary002.Label = 'wall'
FreeCAD.ActiveDocument.CfdFluidBoundary002.ShapeRefs = [
(FreeCAD.ActiveDocument.getObject('Pad'),('Face1','Face3','Face4','Face5','Face7','Face8','Face9','Face11','Face12'))]
FreeCAD.ActiveDocument.recompute()

CfdTools.getActiveAnalysis().addObject(CfdFluidBoundary.makeCfdFluidBoundary())
bc = FreeCAD.ActiveDocument.CfdFluidBoundary003
bc.BoundaryType = 'outlet'
bc.BoundarySubType = 'staticPressureOutlet'
bc.ThermalBoundaryType = 'fixedValue'
bc.Pressure = '0 kg/(mm*s^2)'
bc.Temperature = '293 K'
FreeCAD.ActiveDocument.CfdFluidBoundary003.Label = 'outlet'
FreeCAD.ActiveDocument.CfdFluidBoundary003.ShapeRefs = [
(FreeCAD.ActiveDocument.getObject('Pad'),('Face6',))]
FreeCAD.ActiveDocument.recompute()

init = FreeCAD.ActiveDocument.InitialiseFields
init.PotentialFlow = True
init.UseInletUValues = False
init.Ux = '0 mm/s'
init.Uy = '0 mm/s'
init.Uz = '0 mm/s'
init.UseOutletPValue = True
init.BoundaryP = FreeCAD.ActiveDocument.CfdFluidBoundary003
init.Pressure = '0 kg/(mm*s^2)'
init.VolumeFractions = {}
init.UseInletTemperatureValue = False
init.Temperature = '293 K'
init.UseInletTurbulenceValues = False
init.omega = '57.3 deg/s'
init.k = '0 mm^2/s^2'
init.BoundaryU = None
