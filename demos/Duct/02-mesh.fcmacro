import CfdAnalysis
analysis = CfdAnalysis.makeCfdAnalysis('CfdAnalysis')
import CfdTools
CfdTools.setActiveAnalysis(analysis)
import CfdPhysicsSelection
analysis.addObject(CfdPhysicsSelection.makeCfdPhysicsSelection())
import core.materials.CfdFluidMaterial as CfdFluidMaterial
analysis.addObject(CfdFluidMaterial.makeCfdFluidMaterial('FluidProperties'))
import CfdInitialiseFlowField
analysis.addObject(CfdInitialiseFlowField.makeCfdInitialFlowField())
import CfdSolverFoam
analysis.addObject(CfdSolverFoam.makeCfdSolverFoam())

obj = FreeCAD.ActiveDocument.PhysicsModel
obj.Time = 'Steady'
obj.Flow = 'Incompressible'
obj.Thermal = 'None'
obj.Turbulence = 'Laminar'
obj.gx = '0 mm/s^2'
obj.gy = '-9810 mm/s^2'
obj.gz = '0 mm/s^2'

FreeCAD.ActiveDocument.FluidProperties.Material = {'Name': 'Air', 'Description': 'Standard air properties at 20 Degrees Celsius and 1 atm', 'Density': '1.20 kg/m^3', 'DynamicViscosity': '1.80e-5 kg/m/s', 'MolarMass': '0.0289643897748887 kg/mol', 'Cp': '1004.703 J/kg/K', 'SutherlandConstant': '1.4579326545176254e-06 kg/m/s/K^0.5', 'SutherlandTemperature': '110.4 K'}

import CfdMesh
CfdMesh.makeCfdMesh('Fusion_Mesh')
App.ActiveDocument.ActiveObject.Part = App.ActiveDocument.Fusion
CfdTools.getActiveAnalysis().addObject(App.ActiveDocument.ActiveObject)

FreeCAD.ActiveDocument.Fusion_Mesh.CharacteristicLengthMax = '10 mm'
FreeCAD.ActiveDocument.Fusion_Mesh.MeshUtility = 'snappyHexMesh'
FreeCAD.ActiveDocument.Fusion_Mesh.ElementDimension = '3D'
FreeCAD.ActiveDocument.Fusion_Mesh.CellsBetweenLevels = 3
FreeCAD.ActiveDocument.Fusion_Mesh.EdgeRefinement = 1.0
FreeCAD.ActiveDocument.Fusion_Mesh.PointInMesh = {'x': '487.7 mm', 'y': '41.5 mm', 'z': '54.03 mm'}

import CfdFluidBoundary
CfdTools.getActiveAnalysis().addObject(CfdFluidBoundary.makeCfdFluidBoundary())

bc = FreeCAD.ActiveDocument.CfdFluidBoundary
bc.BoundaryType = 'inlet'
bc.BoundarySubType = 'uniformVelocityInlet'
bc.ThermalBoundaryType = 'fixedValue'
bc.VelocityIsCartesian = True
bc.Ux = '0 mm/s'
bc.Uy = '0 mm/s'
bc.Uz = '-5000 mm/s'
bc.Temperature = '293 K'
FreeCAD.ActiveDocument.CfdFluidBoundary.Label = 'inlet'
FreeCAD.ActiveDocument.CfdFluidBoundary.ShapeRefs = [
(FreeCAD.ActiveDocument.getObject('Fusion'), ('Face8',))]
FreeCAD.ActiveDocument.recompute()

CfdTools.getActiveAnalysis().addObject(CfdFluidBoundary.makeCfdFluidBoundary())

bc = FreeCAD.ActiveDocument.CfdFluidBoundary001
bc.BoundaryType = 'outlet'
bc.BoundarySubType = 'staticPressureOutlet'
bc.ThermalBoundaryType = 'fixedValue'
bc.Pressure = '0 kg/(mm*s^2)'
bc.Temperature = '293 K'
FreeCAD.ActiveDocument.CfdFluidBoundary001.Label = 'outlet'
FreeCAD.ActiveDocument.CfdFluidBoundary001.ShapeRefs = [
(FreeCAD.ActiveDocument.getObject('Fusion'), ('Face12'))]
FreeCAD.ActiveDocument.recompute()

CfdTools.getActiveAnalysis().addObject(CfdFluidBoundary.makeCfdFluidBoundary())

bc = FreeCAD.ActiveDocument.CfdFluidBoundary002
bc.BoundaryType = 'wall'
bc.BoundarySubType = 'fixedWall'
bc.ThermalBoundaryType = 'fixedValue'
bc.VelocityIsCartesian = True
bc.Ux = '0 mm/s'
bc.Uy = '0 mm/s'
bc.Uz = '0 mm/s'
bc.Temperature = '293 K'
FreeCAD.ActiveDocument.CfdFluidBoundary002.Label = 'wall'
FreeCAD.ActiveDocument.CfdFluidBoundary002.ShapeRefs = [
(FreeCAD.ActiveDocument.getObject('Fusion'), ('Face1', 'Face2', 'Face3', 'Face4', 'Face5', 'Face6', 'Face7', 'Face9', 'Face10', 'Face11', 'Face13', 'Face14'))]
FreeCAD.ActiveDocument.recompute()

init = FreeCAD.ActiveDocument.InitialiseFields
init.PotentialFlow = True
init.Ux = '0 mm/s'
init.Uy = '0 mm/s'
init.Uz = '0 mm/s'
init.UseOutletPValue = True
init.BoundaryP = FreeCAD.ActiveDocument.CfdFluidBoundary001
init.Pressure = '0 kg/(mm*s^2)'
init.VolumeFractions = {}
init.Temperature = '293 K'
init.omega = '57.3 deg/s'
init.k = '10000 mm^2/s^2'
