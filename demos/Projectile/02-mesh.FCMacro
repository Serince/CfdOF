import FreeCAD
import CfdAnalysis
import CfdTools
import CfdPhysicsSelection
import core.materials.CfdFluidMaterial as CfdFluidMaterial
import CfdInitialiseFlowField
import CfdSolverFoam
import CfdMesh
import CfdMeshRefinement

analysis = CfdAnalysis.makeCfdAnalysis('CfdAnalysis')
CfdTools.setActiveAnalysis(analysis)
analysis.addObject(CfdPhysicsSelection.makeCfdPhysicsSelection())
analysis.addObject(CfdFluidMaterial.makeCfdFluidMaterial('FluidProperties'))
analysis.addObject(CfdInitialiseFlowField.makeCfdInitialFlowField())
analysis.addObject(CfdSolverFoam.makeCfdSolverFoam())

obj = FreeCAD.ActiveDocument.PhysicsModel
obj.Time = 'Steady'
obj.Phase = 'Single'
obj.Flow = 'HighMachCompressible'
obj.Thermal = 'Energy'
obj.Turbulence = 'RANS'
obj.TurbulenceModel = 'kOmegaSST'
obj.gx = '0 m/s^2'
obj.gy = '-9,81 m/s^2'
obj.gz = '0 m/s^2'

FreeCAD.ActiveDocument.FluidProperties.Material = {'CardName': 'Air', 'AuthorAndLicense': 'Air', 'Name': 'Air', 'Description': 'Standard air properties at 20 Degrees Celsius and 1 atm', 'Density': '1.20 kg/m^3', 'DynamicViscosity': '1.80e-5 kg/m/s', 'MolarMass': '0.0289643897748887 kg/mol', 'Cp': '1004.703 J/kg/K', 'SutherlandTemperature': '110.4 K', 'SutherlandRefViscosity': '1.716e-5 kg/m/s', 'SutherlandRefTemperature': '273.15 K'}

FreeCAD.ActiveDocument.getObject('CfdSolver').MaxIterations = 1000

CfdMesh.makeCfdMesh('Compound_Mesh')
App.ActiveDocument.ActiveObject.Part = App.ActiveDocument.Compound001
CfdTools.getActiveAnalysis().addObject(App.ActiveDocument.ActiveObject)
FreeCAD.ActiveDocument.Compound_Mesh.CharacteristicLengthMax = '225.0 mm'
FreeCAD.ActiveDocument.Compound_Mesh.MeshUtility = 'cfMesh'
FreeCAD.ActiveDocument.Compound_Mesh.ElementDimension = '3D'
FreeCAD.ActiveDocument.Compound_Mesh.CellsBetweenLevels = 3
FreeCAD.ActiveDocument.Compound_Mesh.EdgeRefinement = 1.0
FreeCAD.ActiveDocument.Compound_Mesh.PointInMesh = {'x': '0.0 mm', 'y': '0.0 mm', 'z': '0.0 mm'}

CfdMeshRefinement.makeCfdMeshRefinement(App.ActiveDocument.Compound_Mesh)
FreeCAD.ActiveDocument.MeshRefinement.RelativeLength = 0.015
FreeCAD.ActiveDocument.MeshRefinement.RefinementThickness = '5 mm'
FreeCAD.ActiveDocument.MeshRefinement.NumberLayers = 10
FreeCAD.ActiveDocument.MeshRefinement.ExpansionRatio = 1.05
FreeCAD.ActiveDocument.MeshRefinement.FirstLayerHeight = '0.0 mm'
FreeCAD.ActiveDocument.MeshRefinement.RegionEdgeRefinement = 1.0
FreeCAD.ActiveDocument.MeshRefinement.Internal = False
FreeCAD.ActiveDocument.MeshRefinement.ShapeRefs = [
(FreeCAD.ActiveDocument.getObject('body001001'), ('',))]
FreeCAD.ActiveDocument.recompute()

import CfdMeshRefinement
CfdMeshRefinement.makeCfdMeshRefinement(App.ActiveDocument.Compound_Mesh)
FreeCAD.ActiveDocument.MeshRefinement001.RelativeLength = 0.007
FreeCAD.ActiveDocument.MeshRefinement001.RefinementThickness = '5 mm'
FreeCAD.ActiveDocument.MeshRefinement001.NumberLayers = 10
FreeCAD.ActiveDocument.MeshRefinement001.ExpansionRatio = 1.05
FreeCAD.ActiveDocument.MeshRefinement001.FirstLayerHeight = '0.0 mm'
FreeCAD.ActiveDocument.MeshRefinement001.RegionEdgeRefinement = 1.0
FreeCAD.ActiveDocument.MeshRefinement001.Internal = False
FreeCAD.ActiveDocument.MeshRefinement001.ShapeRefs = [
(FreeCAD.ActiveDocument.getObject('fin2001001'), ('',)),
(FreeCAD.ActiveDocument.getObject('fin1001001'), ('',)),
(FreeCAD.ActiveDocument.getObject('fin3001001'), ('',)),
(FreeCAD.ActiveDocument.getObject('fin4001001'), ('',))]
FreeCAD.ActiveDocument.recompute()

App.ActiveDocument.addObject("Part::Cylinder","Cylinder")
App.ActiveDocument.ActiveObject.Label = "Cylinder"
App.ActiveDocument.recompute()

App.ActiveDocument.getObject('Cylinder').Radius = '50 mm'
App.ActiveDocument.getObject('Cylinder').Height = '480 mm'
App.ActiveDocument.getObject('Cylinder').Placement = App.Placement(App.Vector(-450,0,0),App.Rotation(App.Vector(0,1,0),90))

CfdMeshRefinement.makeCfdMeshRefinement(App.ActiveDocument.Compound_Mesh)
FreeCAD.ActiveDocument.MeshRefinement002.RelativeLength = 0.03
FreeCAD.ActiveDocument.MeshRefinement002.Internal = True
FreeCAD.ActiveDocument.MeshRefinement002.ShapeRefs = [
(FreeCAD.ActiveDocument.getObject('Cylinder'), ('Solid1'))]
App.ActiveDocument.Cylinder.Visibility = False
App.ActiveDocument.recompute()

App.ActiveDocument.addObject("Part::Cylinder","Cylinder")
App.ActiveDocument.ActiveObject.Label = "Cylinder"
App.ActiveDocument.recompute()

FreeCAD.getDocument('modifiedFinner').getObject('Cylinder001').Radius = '100 mm'
FreeCAD.getDocument('modifiedFinner').getObject('Cylinder001').Height = '650 mm'
FreeCAD.getDocument('modifiedFinner').getObject('Cylinder001').Placement = App.Placement(App.Vector(-600,0,0),App.Rotation(App.Vector(0,1,0),90))

CfdMeshRefinement.makeCfdMeshRefinement(App.ActiveDocument.Compound_Mesh)
FreeCAD.ActiveDocument.MeshRefinement003.RelativeLength = 0.06
FreeCAD.ActiveDocument.MeshRefinement003.Internal = True
FreeCAD.ActiveDocument.MeshRefinement003.ShapeRefs = [
(FreeCAD.ActiveDocument.getObject('Cylinder001'), ('Solid1'))]
App.ActiveDocument.Cylinder001.Visibility = False
App.ActiveDocument.recompute()

App.ActiveDocument.addObject("Part::Cylinder","Cylinder")
App.ActiveDocument.ActiveObject.Label = "Cylinder"
App.ActiveDocument.recompute()

App.ActiveDocument.getObject('Cylinder002').Radius = '200 mm'
App.ActiveDocument.getObject('Cylinder002').Height = '900 mm'
App.ActiveDocument.getObject('Cylinder002').Placement = App.Placement(App.Vector(-800,0,0),App.Rotation(App.Vector(0,1,0),90))

CfdMeshRefinement.makeCfdMeshRefinement(App.ActiveDocument.Compound_Mesh)
FreeCAD.ActiveDocument.MeshRefinement004.RelativeLength = 0.12
FreeCAD.ActiveDocument.MeshRefinement004.Internal = True
FreeCAD.ActiveDocument.MeshRefinement004.ShapeRefs = [
(FreeCAD.ActiveDocument.getObject('Cylinder002'), ('Solid1'))]
App.ActiveDocument.Cylinder002.Visibility = False
App.ActiveDocument.recompute()

App.ActiveDocument.addObject("Part::Cylinder","Cylinder")
App.ActiveDocument.ActiveObject.Label = "Cylinder"
App.ActiveDocument.recompute()

App.ActiveDocument.getObject('Cylinder003').Radius = '400 mm'
App.ActiveDocument.getObject('Cylinder003').Height = '1200 mm'
App.ActiveDocument.getObject('Cylinder003').Placement = App.Placement(App.Vector(-1000,0,0),App.Rotation(App.Vector(0,1,0),90))

CfdMeshRefinement.makeCfdMeshRefinement(App.ActiveDocument.Compound_Mesh)
FreeCAD.ActiveDocument.MeshRefinement005.RelativeLength = 0.12
FreeCAD.ActiveDocument.MeshRefinement005.Internal = True
FreeCAD.ActiveDocument.MeshRefinement005.ShapeRefs = [
(FreeCAD.ActiveDocument.getObject('Cylinder003'), ('Solid1'))]
App.ActiveDocument.Cylinder003.Visibility = False
App.ActiveDocument.recompute()
