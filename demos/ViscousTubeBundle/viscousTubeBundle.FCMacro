# -*- coding: utf-8 -*-

import os
FreeCAD.open(os.path.join(os.path.dirname(__file__), "viscousTubeBundle.fcstd"))

Gui.activateWorkbench("CfdOFWorkbench")
import CfdAnalysis
import CfdTools
analysis = CfdAnalysis.makeCfdAnalysis('CfdAnalysis')
CfdTools.setActiveAnalysis(analysis)
import CfdPhysicsSelection
analysis.addObject(CfdPhysicsSelection.makeCfdPhysicsSelection())
import core.materials.CfdFluidMaterial as CfdFluidMaterial
analysis.addObject(CfdFluidMaterial.makeCfdFluidMaterial('FluidProperties'))
import CfdInitialiseFlowField
analysis.addObject(CfdInitialiseFlowField.makeCfdInitialFlowField())
import CfdSolverFoam
analysis.addObject(CfdSolverFoam.makeCfdSolverFoam())
import CfdMesh
CfdMesh.makeCfdMesh('Cut_Mesh')
App.ActiveDocument.ActiveObject.Part = App.ActiveDocument.Cut
CfdTools.getActiveAnalysis().addObject(App.ActiveDocument.ActiveObject)

FreeCAD.ActiveDocument.Cut_Mesh.CharacteristicLengthMax = '10 mm'
FreeCAD.ActiveDocument.Cut_Mesh.MeshUtility = 'cfMesh'
FreeCAD.ActiveDocument.Cut_Mesh.ElementDimension = '2D'
FreeCAD.ActiveDocument.Cut_Mesh.CellsBetweenLevels = 3
FreeCAD.ActiveDocument.Cut_Mesh.EdgeRefinement = 1.0
FreeCAD.ActiveDocument.Cut_Mesh.PointInMesh = {'x': '0 mm', 'y': '0 mm', 'z': '0 mm'}

import CfdMeshRefinement
CfdMeshRefinement.makeCfdMeshRefinement(App.ActiveDocument.Cut_Mesh)
FreeCAD.ActiveDocument.MeshRefinement.ShapeRefs = [
(FreeCAD.ActiveDocument.getObject('Cut'), ('Face7', 'Face9', 'Face11', 'Face13', 'Face15', 'Face6', 'Face25', 'Face23', 'Face21', 'Face19'))]

FreeCAD.ActiveDocument.MeshRefinement.RelativeLength = 0.5
FreeCAD.ActiveDocument.MeshRefinement.RefinementThickness = '5 mm'
FreeCAD.ActiveDocument.MeshRefinement.NumberLayers = 16
FreeCAD.ActiveDocument.MeshRefinement.ExpansionRatio = 1.2
FreeCAD.ActiveDocument.MeshRefinement.FirstLayerHeight = '0 mm'
FreeCAD.ActiveDocument.MeshRefinement.RegionEdgeRefinement = 1.0
FreeCAD.ActiveDocument.MeshRefinement.Internal = False

CfdMeshRefinement.makeCfdMeshRefinement(App.ActiveDocument.Cut_Mesh)
obj = FreeCAD.ActiveDocument.MeshRefinement001
obj.Extrusion = True
obj.ExtrusionType = '2DPlanar'
obj.ExtrusionThickness = '1.0 mm'
FreeCAD.ActiveDocument.MeshRefinement001.ShapeRefs = [
(FreeCAD.ActiveDocument.getObject('Cut'), ('Face3',))]
FreeCAD.ActiveDocument.recompute()

obj = FreeCAD.ActiveDocument.PhysicsModel
obj.Time = 'Steady'
obj.Flow = 'Incompressible'
obj.Thermal = 'None'
obj.Turbulence = 'RANS'
obj.TurbulenceModel = 'kOmegaSST'
obj.gx = '0 mm/s^2'
obj.gy = '-9810 mm/s^2'
obj.gz = '0 mm/s^2'

FreeCAD.ActiveDocument.FluidProperties.Material = {'Name': 'Air', 'Description': 'Standard air properties at 20 Degrees Celsius and 1 atm', 'Density': '1.20 kg/m^3', 'DynamicViscosity': '1.80e-5 kg/m/s', 'MolarMass': '0.0289643897748887 kg/mol', 'Cp': '1004.703 J/kg/K', 'SutherlandConstant': '1.4579326545176254e-06 kg/m/s/K^0.5', 'SutherlandTemperature': '110.4 K'}

FreeCAD.ActiveDocument.CfdSolver.MaxIterations = 500
FreeCAD.ActiveDocument.CfdSolver.SteadyWriteInterval = 50

import CfdFluidBoundary
CfdTools.getActiveAnalysis().addObject(CfdFluidBoundary.makeCfdFluidBoundary())

bc = FreeCAD.ActiveDocument.CfdFluidBoundary
bc.BoundaryType = 'inlet'
bc.BoundarySubType = 'uniformVelocityInlet'
bc.ThermalBoundaryType = 'fixedValue'
bc.VelocityIsCartesian = True
bc.Ux = '1000 mm/s'
bc.Uy = '0 mm/s'
bc.Uz = '0 mm/s'
bc.VelocityMag = '0 mm/s'
bc.DirectionFace = ''
bc.ReverseNormal = True
bc.MassFlowRate = '0 kg/s'
bc.VolFlowRate = '0 mm^3/s'
bc.Pressure = '0 kg/(mm*s^2)'
bc.SlipRatio = '0 '
bc.Temperature = '293 K'
bc.HeatFlux = '0 kg/s^3'
bc.HeatTransferCoeff = '0 kg/(s^3*K)'
bc.TurbulenceInletSpecification = 'intensityAndLengthScale'
bc.TurbulentKineticEnergy = '10000 mm^2/s^2'
bc.SpecificDissipationRate = '57.3 deg/s'
bc.TurbulenceIntensityPercentage = '5 '
bc.TurbulenceLengthScale = '2 mm'
bc.PorousBaffleMethod = 'porousCoeff'
bc.PressureDropCoeff = '0 '
bc.ScreenWireDiameter = '0.1 mm'
bc.ScreenSpacing = '0 mm'
FreeCAD.ActiveDocument.CfdFluidBoundary.Label = 'inlet'
FreeCAD.ActiveDocument.CfdFluidBoundary.ShapeRefs = [(FreeCAD.ActiveDocument.getObject('Cut'), ('Face1',))]
FreeCAD.ActiveDocument.recompute()

CfdTools.getActiveAnalysis().addObject(CfdFluidBoundary.makeCfdFluidBoundary())

bc = FreeCAD.ActiveDocument.CfdFluidBoundary001
bc.BoundaryType = 'outlet'
bc.BoundarySubType = 'staticPressureOutlet'
bc.ThermalBoundaryType = 'fixedValue'
bc.VelocityIsCartesian = True
bc.Ux = '0 mm/s'
bc.Uy = '0 mm/s'
bc.Uz = '0 mm/s'
bc.VelocityMag = '0 mm/s'
bc.DirectionFace = ''
bc.ReverseNormal = False
bc.MassFlowRate = '0 kg/s'
bc.VolFlowRate = '0 mm^3/s'
bc.Pressure = '0 kg/(mm*s^2)'
bc.SlipRatio = '0 '
bc.Temperature = '293 K'
bc.HeatFlux = '0 kg/s^3'
bc.HeatTransferCoeff = '0 kg/(s^3*K)'
bc.TurbulenceInletSpecification = 'intensityAndLengthScale'
bc.TurbulentKineticEnergy = '10000 mm^2/s^2'
bc.SpecificDissipationRate = '57.3 deg/s'
bc.TurbulenceIntensityPercentage = '10 '
bc.TurbulenceLengthScale = '100 mm'
bc.PorousBaffleMethod = 'porousCoeff'
bc.PressureDropCoeff = '0 '
bc.ScreenWireDiameter = '0.1 mm'
bc.ScreenSpacing = '0 mm'
FreeCAD.ActiveDocument.CfdFluidBoundary001.Label = 'outlet'
FreeCAD.ActiveDocument.CfdFluidBoundary001.ShapeRefs = [(FreeCAD.ActiveDocument.getObject('Cut'), ('Face17'))]
FreeCAD.ActiveDocument.recompute()

CfdTools.getActiveAnalysis().addObject(CfdFluidBoundary.makeCfdFluidBoundary())

bc = FreeCAD.ActiveDocument.CfdFluidBoundary002
bc.BoundaryType = 'wall'
bc.BoundarySubType = 'fixedWall'
bc.ThermalBoundaryType = 'fixedValue'
bc.VelocityIsCartesian = True
bc.Ux = '0 mm/s'
bc.Uy = '0 mm/s'
bc.Uz = '0 mm/s'
bc.VelocityMag = '0 mm/s'
bc.DirectionFace = ''
bc.ReverseNormal = False
bc.MassFlowRate = '0 kg/s'
bc.VolFlowRate = '0 mm^3/s'
bc.Pressure = '0 kg/(mm*s^2)'
bc.SlipRatio = '0 '
bc.Temperature = '293 K'
bc.HeatFlux = '0 kg/s^3'
bc.HeatTransferCoeff = '0 kg/(s^3*K)'
bc.TurbulenceInletSpecification = 'intensityAndLengthScale'
bc.TurbulentKineticEnergy = '10000 mm^2/s^2'
bc.SpecificDissipationRate = '57.3 deg/s'
bc.TurbulenceIntensityPercentage = '10 '
bc.TurbulenceLengthScale = '100 mm'
bc.PorousBaffleMethod = 'porousCoeff'
bc.PressureDropCoeff = '0 '
bc.ScreenWireDiameter = '0.1 mm'
bc.ScreenSpacing = '0 mm'
FreeCAD.ActiveDocument.CfdFluidBoundary002.Label = 'wall'
FreeCAD.ActiveDocument.CfdFluidBoundary002.ShapeRefs = [
(FreeCAD.ActiveDocument.getObject('Cut'), ('Face7', 'Face9', 'Face11', 'Face13', 'Face15', 'Face6', 'Face25', 'Face23', 'Face21', 'Face19'))]
FreeCAD.ActiveDocument.recompute()

init = FreeCAD.ActiveDocument.InitialiseFields
init.PotentialFlow = True
init.Ux = '0 mm/s'
init.Uy = '0 mm/s'
init.Uz = '0 mm/s'
init.UseOutletPValue = True
init.BoundaryP = FreeCAD.ActiveDocument.CfdFluidBoundary001
init.Pressure = '0 kg/(mm*s^2)'
init.VolumeFractions = {}
init.Temperature = '293 K'
init.omega = '57.3 deg/s'
init.k = '10000 mm^2/s^2'

FreeCAD.ActiveDocument.recompute()
